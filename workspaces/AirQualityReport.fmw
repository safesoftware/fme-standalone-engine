FME workspace AirQualityReport.fmw
Title: HTMLReportGenerator

Parameters:
- Location = Boston   # Enter City Name
- SourceDataset_SPATIALITE = https://s3.amazonaws.com/don.demo.safe.com/FMEEngineDemo/TourLocations.sl3   # Source SpatiaLite Database File(s)

Readers:
- SPATIALITE_1: SPATIALITE from $(SourceDataset_SPATIALITE)

wwtour_2016_locations (reader SPATIALITE_1)
    attributes: location string(255), date string(255), host string(255), register string(255), latitude real(20,10), longitude real(20,10), longlat string(255)
    -> Tester_2
Note: Determine the City to run the request against
Note: AQI website: http://aqicn.org / World Map: http://aqicn.org/map/#@g/0/0/2z / HTTP request form / https://wind.waqi.info/mapq/bounds/?bounds=@Value(_indices{0}.y),@Value(_indices{0}.x),@Value(_indices{2}.y),@Value(_indices{2}.x)
Tester_2
    TEST_CLAUSE = TEST @Value(location) CONTAINS $(Location)
    TEST_MODE = Automatic
    TEST_DESCRIPTION = ""
    BOOL_OP = OR
    PASSED -> GeographicBufferer
Note: Buffer the City
GeographicBufferer
    BufferDist = 50
    CAP_STYLE = Round
    BufferUnit = Kilometers
    -> BoundingBoxReplacer
    <Rejected> -> GeographicBufferer__Rejected_
Note: Clean up some attributes
AttributeManager_2
    ATTR_TABLE:
      SET_TO _mapLabel = Location: @Value(city)

        AQI: @Value(aqi) @Value(pol)
      SET_TO _sortIndex = 1
      RENAME_SET_VALUE Initiatorlocation > location
      RENAME_SET_VALUE Initiatordate > date
      RENAME_SET_VALUE Initiatorhost > host
      RENAME_SET_VALUE Initiatorregister > register
      RENAME_SET_VALUE Initiatorlatitude > latitude
      RENAME_SET_VALUE Initiatorlongitude > longitude
      RENAME_SET_VALUE Initiatorlonglat > longlat
      REMOVE Initiator_indices{}.x
      REMOVE Initiator_indices{}.y
      REMOVE Initiator_indices{}.z
      REMOVE Initiatoraqi_query
    -> VertexCreator
Note: Create a point of the reading for the map.
VertexCreator
    XVAL = @Value(lon)
    YVAL = @Value(lat)
    MODE_NAME = Replace with Point
    -> HTMLReportGenerator
Note: Create the report
HTMLReportGenerator
    GROUP_BY = _sortIndex location
    CONTENT_LIST = HEADER HEADER TABLE MAP_ESRI
    TITLE = Air Quality Index
    PAGE_CONFIG = HEADER{{TEXT;Air Quality Index at @Value(location) @Value(utime);HEADER;H3;ALIGNMENT;CENTER;COLOR;0,170,255;FME_CONTROLLER_QUERY_FILE;transformers\dependencies\html5\Header.fme}}HEADER{{TEXT;Sample Data;HEADER;H2;ALIGNMENT;LEFT;COLOR;0,0,255;FME_CONTROLLER_QUERY_FILE;transformers\dependencies\html5\Table.fme}}TABLE{{STYLE;CONDENSED;TABLE;city|Sample Location/aqi|AQI/pol|Pollutant;TABLE_GROUP;;FME_CONTROLLER_QUERY_FILE;transformers\dependencies\html5\Table.fme}}MAP_ESRI{{LABEL;_mapLabel;COLOR;0,0,255;BASEMAP;Streets;URLS;;FME_CONTROLLER_QUERY_FILE;transformers/dependencies/html5/Map (Esri Leaflet).fme}}
    -> FeatureWriter [HTML]
Note: Write it out to a file
FeatureWriter
    DATASET = ../results/AirQualityReport$(Location).html
    FEATURE_TYPE_LIST_ATTR = _feature_type
    FORMAT = HTML
    DATASET_ATTR = _dataset
    TOTAL_FEATURES_WRITTEN_ATTR = _total_features_written
GeographicBufferer__Rejected_: Inspector

Bookmark: Get the Minimum and Max Coordinates
BoundingBoxReplacer
    BOXTYPE = Bounding Box
    BOX -> CoordinateExtractor
CoordinateExtractor
    LIST_NAME = _indices
    MODE = All Coordinates
    -> StringConcatenator

Bookmark: Use the AQI to get the readings for feeds
Note: Build the First URL to query the AQI Service / for the stations in the bounding box.
StringConcatenator
    VAL_ATTR = aqi_query
    ACTION = Create New Attribute
    PARM_LINE = https://wind.waqi.info/mapq/bounds/?bounds=@Value(_indices{0}.y),@Value(_indices{0}.x),@Value(_indices{2}.y),@Value(_indices{2}.x)
    -> FeatureReader [INITIATOR]
FeatureReader
    ATTRIBUTES = JSONFeature,"lat,lon,city,idx,stamp,pol,x,aqi,tz,utime,img,fme_geometry{0}"
    JSON_SCAN_MODE = AUTO
    JSON_USE_SEARCH_ENVELOPE = NO
    COMBINE_GEOM = Use Initiator
    JSON_CLIP_TO_ENVELOPE = NO
    JSON_SAVE_FRAGMENTS = NO
    JSON_DECODE_TEXT_STRINGS = Yes
    DATASET = @Value(aqi_query)
    ATTR_PREFIX = Initiator
    JSON_FLATTEN_MODE = ALL_LEVELS
    JSON_USE_BASENAME_AS_DEFAULT_FEATURE_TYPE = No
    JSON_GEOMETRY_FORMAT = None
    OUTPUT_FEATURES_DISPLAY = Schema and Data Features
    FORMAT = JSON
    ATTR_ACCUM_MODE = Prefix Initiator
    JSON_FEATURE_TYPE_KEY = json_featuretype
    JSONFeature -> AttributeManager_2
